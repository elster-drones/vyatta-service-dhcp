module vyatta-service-dhcp-server-routing-instance-v1 {
	namespace "urn:vyatta.com:mgmt:vyatta-service-dhcp-server-routing-instance:1";
	prefix vyatta-service-dhcp-server-routing-instance-v1;

	import configd-v1 {
		prefix configd;
	}
	import vyatta-service-dhcp-server-v1 {
		prefix server;
	}
	import vyatta-routing-v1 {
		prefix routing;
	}
	import vyatta-interfaces-v1 {
		prefix if;
	}
	import vyatta-interfaces-bridge-v1 {
		prefix if-bridge;
	}
	import vyatta-interfaces-dataplane-v1 {
		prefix if-dataplane;
	}
	import vyatta-interfaces-bonding-v1 {
		prefix if-bonding;
	}
	import vyatta-routing-instance-interfaces-v1 {
		prefix rtintf;
	}

	organization "AT&T Inc.";
	contact
		"AT&T
		 Postal: 208 S. Akard Street
		         Dallas, TX 75202
		 Web: www.att.com";

	description
		"Copyright (c) 2017-2019 AT&T Intellectual Property
		 All rights reserved.

		 Copyright (c) 2016-2017 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-service-dhcp-server-routing-instance-v1";

	revision 2017-12-15 {
		description "Expand grouping to work around interop problem with
                     Cisco NSO";
	}

	revision 2017-03-01 {
		description "Support getting DHCP server leases via Netconf API";
	}

	revision 2016-06-12 {
		description "Initial revision of version 1.";
	}

	augment /routing:routing/routing:routing-instance/routing:service {
		container dhcp-server {
			presence "true";
			configd:priority "911";
			configd:help "Dynamic Host Configuration Protocol (DHCP) for DHCP server";
			configd:end "/opt/vyatta/share/tmplscripts/service/dhcp-server/configd_vrf_end1.cli";
			uses server:dhcp-server-service-config {
				refine listento/interface {
					configd:allowed "vyatta-show-interfaces.pl --vrf=$VAR(../../../../@) --action=dhcp_allowed";
					must "(current() = /if:interfaces/if-dataplane:dataplane/if-dataplane:tagnode)"
						+ "or (substring-after(current(), '.') = /if:interfaces/if-dataplane:dataplane"
						+ "[if-dataplane:tagnode = substring-before(current(), '.')]/if-dataplane:vif/if-dataplane:tagnode)"
						+ "or (current() = /if:interfaces/if-bridge:bridge/if-bridge:tagnode)"
						+ "or (current() = /if:interfaces/if-bonding:bonding/if-bonding:tagnode)"
						+ "or (substring-after(current(), '.') = /if:interfaces/if-bonding:bonding"
						+ "[if-bonding:tagnode = substring-before(current(), '.')]/if-bonding:vif/if-bonding:tagnode)" {
						error-message "Interface name must refer to an existing dataplane, bonding or bridge interface name";
					}
					must "current() = /routing:routing/routing:routing-instance" +
						"[routing:instance-name = current()/../../../../routing:instance-name]" +
						"/rtintf:interface/rtintf:name" {
						error-message "Interface must be configured in this routing instance";
					}
				}
			}
			container state {
				description "DHCPv4 server state for default routing instance";
				config false;
				configd:get-state "/opt/vyatta/bin/dhcp-show-leases.pl --rtinst all --netconf";
				uses server:leases;
			}
		}
	}
}
