module vyatta-service-dhcpv6-server {
	namespace "urn:vyatta.com:mgmt:vyatta-service-dhcpv6-server";
	prefix service-dhcpv6-server;

	import vyatta-types {
		prefix types;
	}
	import vyatta-services {
		prefix service;
	}
	import configd {
		prefix configd;
	}

	organization "AT&T Inc.";
	contact
		"AT&T
		 Postal: 208 S. Akard Street
		         Dallas, TX 75202
		 Web: www.att.com";

	description
		"Copyright (c) 2018-2019 AT&T Intellectual Property
		 All rights reserved.

		 Copyright (c) 2014-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-service-dhcpv6-server";

	revision 2015-03-12 {
		description "moved static-mapping under service dhcpv6-server";
	}
	revision 2015-02-18 {
		description "prefix-length node moved under stop node for prefix-delegation";
	}
	revision 2014-10-28 {
		description "Update for 3.2.1R1";
	}
	
	revision 2014-08-27 {
		description "Initial revision.";
		configd:migration 1;
	}

	augment /service:service {
		container dhcpv6-server {
			presence "true";
			configd:priority "900";
			configd:help "DHCP for IPv6 (DHCPv6) server";
			configd:end "/opt/vyatta/share/tmplscripts/service/dhcpv6-server/configd_end.sh";
			leaf preference {
				type uint32 {
					range 0..255 {
						error-message "Preference must be between 0 and 255";
					}
				}
				configd:help "Preference of this DHCPv6 server compared with others";
			}
			container listento {
				configd:help "force dhcpdv6 listens to interfaces";
				leaf-list interface {
					type string;
					ordered-by "user";
					configd:help "interfaces dhcpdv6 listens to";
					configd:allowed "/opt/vyatta/share/tmplscripts/service/dhcpv6-server/interface/configd_allowed.sh";
					configd:validate "/opt/vyatta/share/tmplscripts/service/dhcpv6-server/configd_validate1.cli";
				}
			}
			list static-mapping {
			     	configd:help "Name of static mapping";
				key "tagnode";
				leaf tagnode {
				     type string;
				     configd:help "Name of static mapping";
				}
				leaf identifier {
				     mandatory true;
				     type string {
					configd:syntax "/opt/vyatta/share/tmplscripts/service/dhcpv6-server/static-mapping/configd_syntax1.cli";
					}
				     configd:help "Client identifier for this static mapping.
you have to use double quote if your duid contains back slash";
				}
				leaf ipv6-address {
				     type types:ipv6-address;
				     configd:help "Client IPv6 address for this static mapping";
				}
			}
			list shared-network-name {
				configd:help "DHCPv6 shared network name [REQUIRED]";
				key "tagnode";
				leaf tagnode {
					type string {
						pattern '[-_a-zA-Z0-9\.]+' {
							configd:error-message "invalid DHCP pool name \"$VAR(@)\"";
						}
					}
					configd:help "DHCPv6 shared network name [REQUIRED]";
				}
				list subnet {
					configd:help "IPv6 DHCP subnet for this shared network [REQUIRED]";
					key "tagnode";
					leaf tagnode {
						type types:ipv6-prefix;
						configd:help "IPv6 DHCP subnet for this shared network [REQUIRED]";
					}
					leaf description {
						type string;
						configd:help "Description of this subnet";
					}
					leaf-list domain-search {
						type string {
							pattern '[-_a-zA-Z0-9\.]+' {
								configd:error-message "invalid domain name syntax \"$VAR(@)\"";
							}
						}
						ordered-by "user";
						configd:help "Domain name for client to search";
					}
					leaf-list nisplus-server {
						type types:ipv6-address;
						ordered-by "user";
						configd:help "IPv6 address of a NIS Plus server";
					}
					leaf-list nis-server {
						type types:ipv6-address;
						ordered-by "user";
						configd:help "IPv6 address of a NIS server";
					}
					container address-range {
						presence "true";
						configd:help "Parameters setting ranges for assigning IPv6 addresses";
						list prefix {
							configd:help "IPv6 prefix defining range of addresses to assign";
							key "tagnode";
							leaf tagnode {
								type types:ipv6-prefix;
								configd:help "IPv6 prefix defining range of addresses to assign";
							}
							leaf temporary {
								type empty;
								configd:help "Address range will be used for temporary addresses";
							}
						}
						list start {
							configd:help "First in range of consecutive IPv6 addresses to assign";
							key "tagnode";
							leaf tagnode {
								type types:ipv6-address;
								configd:help "First in range of consecutive IPv6 addresses to assign";
							}
							leaf stop {
								type types:ipv6-address;
								configd:help "Last in range of consecutive IPv6 addresses";
							}
						}
					}
					leaf nisplus-domain {
						type string {
							pattern '[-_a-zA-Z0-9\.]+' {
								configd:error-message "invalid NIS Plus domain name syntax \"$VAR(@)\"";
							}
						}
						configd:help "NIS Plus domain name for client to use";
					}
					leaf-list sip-server-name {
						type string {
							pattern '[-_a-zA-Z0-9\.]+' {
								configd:error-message "invalid SIP server name syntax \"$VAR(@)\"";
							}
						}
						ordered-by "user";
						configd:help "SIP server name";
					}
					leaf-list name-server {
						type types:ipv6-address;
						ordered-by "user";
						configd:help "IPv6 address of a Recursive DNS Server";
					}
					leaf-list sip-server-address {
						type types:ipv6-address;
						ordered-by "user";
						configd:help "IPv6 address of a SIP name server";
					}
					container prefix-delegation {
						presence "true";
						configd:help "Parameters relating to IPv6 prefix delegation";
						list start {
							configd:help "First in range of IPv6 addresses to be used in prefix delegation";
							key "tagnode";
							leaf tagnode {
								type types:ipv6-address;
								configd:help "First in range of IPv6 addresses to be used in prefix delegation";
							}
							list stop {
								configd:help "Last in range of IPv6 addresses to be used in prefix delegation";
								key "tagnode";
								leaf tagnode {
									type types:ipv6-address;
									configd:help "Last in range of IPv6 addresses to be used in prefix delegation";
								}
								leaf prefix-length {
									type uint32 {
										range 0..128 {
											error-message "Prefix must be between 0 and 128";
										}
									}
									configd:help "Length in bits of prefixes to be delegated";
								}
							}
						}
					}
					leaf-list sntp-server {
						type types:ipv6-address;
						ordered-by "user";
						configd:help "IPv6 address of an SNTP Server for client to use";
					}
					leaf nis-domain {
						type string {
							pattern '[-_a-zA-Z0-9\.]+' {
								configd:error-message "invalid NIS domain name syntax \"$VAR(@)\"";
							}
						}
						configd:help "NIS domain name for client to use";
					}
					container lease-time {
						presence "true";
						configd:help "Parameters relating to the lease time";
						leaf maximum {
							type uint32;
							configd:help "Maximum time (in seconds) that will be assigned to a lease";
						}
						leaf default {
							type uint32;
							configd:help "Default time (in seconds) that will be assigned to a lease";
						}
						leaf minimum {
							type uint32;
							configd:help "Minimum time (in seconds) that will be assigned to a lease";
						}
					}
				}
			}
		}
	}
}
